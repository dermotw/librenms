-- *****************************************************************
-- RBN-SMI.my:	RedBack Networks Structure of Management Information
--
-- Copyright (c) 1998, 2001-2002 RedBack Networks, Inc.
-- All rights reserved.
-- 
-- *****************************************************************

RBN-SMI DEFINITIONS ::= BEGIN

IMPORTS
	MODULE-IDENTITY,
	OBJECT-IDENTITY,
	enterprises
		FROM SNMPv2-SMI;

redBackNetworks MODULE-IDENTITY
	LAST-UPDATED	"200106270000Z" -- June 27, 2001
	ORGANIZATION	"RedBack Networks, Inc."
	CONTACT-INFO
		"	RedBack Networks, Inc.

		Postal:	300 Holger Way
			San Jose, CA  95134
			USA

		 Phone:	+1 408 570-5000
		   Fax: +1 408 570-5599

		E-mail:	mib-info@redback.com"
	DESCRIPTION
		"The Structure of Management Information for
		RedBack Networks"

        REVISION    "200206060000Z" -- June 6, 2002
        DESCRIPTION
                "Updated Contact-info and recovered revision info."

        REVISION    "200106270000Z" -- June 27, 2001
        DESCRIPTION
                "Added rbnInternal."

        REVISION    "9804182300Z" -- April 18, 1998
        DESCRIPTION
                "Initial version."
	::= { enterprises 2352 }

rbnProducts OBJECT-IDENTITY
	STATUS	current
	DESCRIPTION
		""
	::= { redBackNetworks 1 }

rbnMgmt OBJECT-IDENTITY
	STATUS current
	DESCRIPTION
		""
	::= { redBackNetworks 2 }

rbnExperiment OBJECT-IDENTITY
	STATUS current
	DESCRIPTION
		""
	::= { redBackNetworks 3 }

rbnCapabilities OBJECT-IDENTITY
	STATUS current
	DESCRIPTION
		""
	::= { redBackNetworks 4 }

rbnModules OBJECT-IDENTITY
	STATUS current
	DESCRIPTION
		""
	::= { redBackNetworks 5 }

rbnEntities OBJECT-IDENTITY
	STATUS current
	DESCRIPTION
		""
	::= { redBackNetworks 6 }

rbnInternal OBJECT-IDENTITY
	STATUS current
	DESCRIPTION
		""
	::= { redBackNetworks 7 }

END
