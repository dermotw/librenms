-- *****************************************************************
-- RBN-AAL5-VCL-STAT-MIB
--
-- Copyright (c) 1998, 2002 RedBack Networks, Inc.
-- All rights reserved.
-- 
-- *****************************************************************

RBN-AAL5-VCL-STAT-MIB DEFINITIONS ::= BEGIN

IMPORTS
	MODULE-IDENTITY,
	OBJECT-TYPE,
	Counter32
		FROM SNMPv2-SMI
	MODULE-COMPLIANCE,
	OBJECT-GROUP
		FROM SNMPv2-CONF
	rbnXAtmAal5VclStatEntry
		FROM RBN-X-AAL5-VCL-STAT-MIB
	rbnMgmt
		FROM RBN-SMI;

rbnAal5VclStatMIB MODULE-IDENTITY
	LAST-UPDATED	"200205290000Z"
	ORGANIZATION	"RedBack Networks, Inc."
	CONTACT-INFO
		"      RedBack Networks, Inc.

               Postal: 300 Holger Way
                       San Jose, CA 95134
                       USA

                       Phone: +1 408 750 5000
                         Fax: +1 408 750 5599

		E-mail:	mib-info@RedBackNetworks.com"
	DESCRIPTION
		"The MIB for instrumenting statistics associated with
		an ATM VCL beyond those instrumented by standards-track
		MIBs."
        REVISION      "200205290000Z" -- May 29, 2002
        DESCRIPTION
                "remove unused IMPORTs. Update CONTACT-INFO"
        REVISION        "9804171645Z"
        DESCRIPTION
	        "Initial version."
	::= { rbnMgmt 1 }


rbnAal5VclStatMIBObjects OBJECT IDENTIFIER ::= { rbnAal5VclStatMIB 1 }

rbnAtmAal5VclStatTable   OBJECT-TYPE
	SYNTAX       SEQUENCE OF RbnAtmAal5VclStatEntry
	MAX-ACCESS   not-accessible
	STATUS       current
	DESCRIPTION
		"This table provides a collection of auxiliary
		objects	providing AAL5 configuration and performance
		statistics of a VCL."
	::= { rbnAal5VclStatMIBObjects 1 }

rbnAtmAal5VclStatEntry    OBJECT-TYPE
	SYNTAX       RbnAtmAal5VclStatEntry
	MAX-ACCESS   not-accessible
	STATUS       current
	DESCRIPTION
		"Each entry in this table represents a VCL."
--	AUGMENTS { atmAal5VclStatEntry } when it becomes standards-track
	AUGMENTS { rbnXAtmAal5VclStatEntry }
	::= { rbnAtmAal5VclStatTable 1 }


RbnAtmAal5VclStatEntry ::=
	SEQUENCE {
		rbnAtmAal5VclOutDrops	Counter32
	}


rbnAtmAal5VclOutDrops OBJECT-TYPE
	SYNTAX       Counter32
	MAX-ACCESS   read-only
	STATUS       current
	DESCRIPTION
		"The number of AAL5 CPCS PDUs received for transmission
		on the AAL5 VCC at the interface identified by the
		ifIndex which were chosen to be dropped even though
		no errors had been detected to prevent their being
		transmitted.  One possible reason for dropping such a
		PDU could be a lack of available space on the interface
		output queue."
	::= { rbnAtmAal5VclStatEntry 1 }


-- Conformance Information

rbnAal5VclStatMIBConformance OBJECT IDENTIFIER ::=
	{ rbnAal5VclStatMIB 2 }

rbnAal5VclStatMIBGroups OBJECT IDENTIFIER ::= 
	{ rbnAal5VclStatMIBConformance 1 }

rbnAal5VclStatMIBCompliances OBJECT IDENTIFIER ::=
	{ rbnAal5VclStatMIBConformance 2 }


-- Compliance Statements

rbnAal5VclStatMIBCompliance MODULE-COMPLIANCE
	STATUS	    current
	DESCRIPTION
		"The compliance statement for RedBack Networks
		SNMP entities which represent AAL5 VCL statistics"
	MODULE	    -- this module
	MANDATORY-GROUPS {
		rbnAal5VclStatGroup
		}
	::= { rbnAal5VclStatMIBCompliances 1 }

-- Units of Conformance

rbnAal5VclStatGroup OBJECT-GROUP
	OBJECTS {
		rbnAtmAal5VclOutDrops
	}
	STATUS	    current
	DESCRIPTION
		"A collection of objects providing supplemental
		AAL5 VCL information beyond that supplied by
		IETF standards-track MIBs"
	::= { rbnAal5VclStatMIBGroups 1 }

END
