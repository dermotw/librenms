-- *****************************************************************
-- RBN-IPPOOL-MIB	Redback IP Pool Mib
--
-- Copyright (c) 2001-2002, 2004 RedBack Networks, Inc.
-- All rights reserved.
-- 
-- *****************************************************************

RBN-IPPOOL-MIB DEFINITIONS ::= BEGIN

IMPORTS
	MODULE-IDENTITY, OBJECT-TYPE, NOTIFICATION-TYPE,
	Unsigned32, IpAddress
		FROM SNMPv2-SMI

        TruthValue
                FROM SNMPv2-TC

	MODULE-COMPLIANCE,
	OBJECT-GROUP,
	NOTIFICATION-GROUP
		FROM SNMPv2-CONF

	SnmpAdminString
		FROM SNMP-FRAMEWORK-MIB

	rbnMgmt
		FROM RBN-SMI;

rbnIpPoolMib MODULE-IDENTITY
	LAST-UPDATED	"200111071700Z" -- Nov 7, 2001
	ORGANIZATION	"Redback Networks, Inc."
        CONTACT-INFO
                "       RedBack Networks, Inc.

                Postal: 300 Holger Way
                        San Jose, CA  95134-1362
                        USA

                 Phone: +1 408 750 5000
                   Fax: +1 408 750 5599

                E-mail: mib-info@redback.com"
	DESCRIPTION
		"Defines the objects necessary to obtain information about
		IP Pools for interfaces within a context."

	REVISION	"200111071700Z" -- Nov 7, 2001
	DESCRIPTION
		"Initial version."

	::= { rbnMgmt 15 }


rbnIpPoolMIBNotifications OBJECT IDENTIFIER ::= { rbnIpPoolMib 0 }

rbnIpPoolMIBObjects       OBJECT IDENTIFIER ::= { rbnIpPoolMib 1 }

rbnIpPoolMIBConformance   OBJECT IDENTIFIER ::= { rbnIpPoolMib 2 }


--
-- IP Pool Table
--

rbnIpPoolTable OBJECT-TYPE
	SYNTAX       SEQUENCE OF RbnIpPoolEntry
	MAX-ACCESS   not-accessible
	STATUS       current
	DESCRIPTION
		"The purpose of this table is to allow customers to monitor
		the status of IP Pools on their SMS systems through SNMP.

		This table contains the objects which identify information
		about IP Pools.  Each row in the table corresponds to one
		IP Pool for a given interface within a particular
		context.

		Objects defined in this table are only accessible within the
		context identified in the SNMP protocol (i.e. the community
		string in v1/v2c or the contextName in v3)."
	::= { rbnIpPoolMIBObjects 1 }

rbnIpPoolEntry OBJECT-TYPE
	SYNTAX       RbnIpPoolEntry
	MAX-ACCESS   not-accessible
	STATUS       current
	DESCRIPTION
		"A conceptual row in the rbnIpPoolTable."
	INDEX        { rbnIpPoolInterfaceIdx, rbnIpPoolAddr }
	::= { rbnIpPoolTable 1 }

RbnIpPoolEntry ::=
	SEQUENCE {
		rbnIpPoolInterfaceIdx	Unsigned32,
		rbnIpPoolAddr		IpAddress,
		rbnIpPoolInterfaceName	SnmpAdminString,
		rbnIpPoolMask		IpAddress,
		rbnIpPoolSize		Unsigned32,
		rbnIpPoolAvailable	Unsigned32,
		rbnIpPoolUnusable	Unsigned32,
		rbnIpPoolInuse		Unsigned32,
		rbnIpPoolThreshold	Unsigned32,
		rbnIpPoolSendTrap	TruthValue,
		rbnIpPoolLogMessage	TruthValue
	}

rbnIpPoolInterfaceIdx OBJECT-TYPE
	SYNTAX       Unsigned32
	MAX-ACCESS   not-accessible
	STATUS       current
	DESCRIPTION
		"The index of the interface containing the IP Pool."
	::= { rbnIpPoolEntry 1 }

rbnIpPoolAddr OBJECT-TYPE
	SYNTAX       IpAddress
	MAX-ACCESS   not-accessible
	STATUS       current
	DESCRIPTION
		"The start address of the IP Pool."
	::= { rbnIpPoolEntry 2 }

rbnIpPoolInterfaceName OBJECT-TYPE
	SYNTAX       SnmpAdminString (SIZE (0..127))
	MAX-ACCESS   read-only
	STATUS       current
	DESCRIPTION
		"The name of the interface containing the IP Pool."
	::= { rbnIpPoolEntry 3 }

rbnIpPoolMask OBJECT-TYPE
	SYNTAX       IpAddress
	MAX-ACCESS   read-only
	STATUS       current
	DESCRIPTION
		"The subnet mask of the IP Pool."
	::= { rbnIpPoolEntry 4 }

rbnIpPoolSize OBJECT-TYPE
	SYNTAX       Unsigned32
	MAX-ACCESS   read-only
	STATUS       current
	DESCRIPTION
		"The size of the IP Pool is defined to be the sum of
		 the available addresses plus the unusable addresses."
	::= { rbnIpPoolEntry 5 }

rbnIpPoolAvailable OBJECT-TYPE
	SYNTAX       Unsigned32
	MAX-ACCESS   read-only
	STATUS       current
	DESCRIPTION
		"The number of addresses of an IP Pool that are available."
	::= { rbnIpPoolEntry 6 }

rbnIpPoolUnusable OBJECT-TYPE
	SYNTAX       Unsigned32
	MAX-ACCESS   read-only
	STATUS       current
	DESCRIPTION
		"Unusable IP addresses in an IP Pool consist of the
		 ip address of the interface, and those used by the
		 network address and the broadcast address of the
		 interface."
	::= { rbnIpPoolEntry 7 }

rbnIpPoolInuse OBJECT-TYPE
	SYNTAX       Unsigned32
	MAX-ACCESS   read-only
	STATUS       current
	DESCRIPTION
		"The number of addresses of an IP Pool that are in use."
	::= { rbnIpPoolEntry 8 }

rbnIpPoolThreshold OBJECT-TYPE
	SYNTAX       Unsigned32 (0..65535)
	MAX-ACCESS   read-only
	STATUS       current
	DESCRIPTION
		"The threshold of an IP Pool is the value for currently
		available addresses, as reported in rbnIpPoolAvailable,
		which causes a trap and/or log message to be generated
		when this value is reached.

		This is a falling threshold, so a trap and/or log message
		will only be sent on a transition of the value of available
		addresss from (rbnIpPoolThreshold+1) addresses to
		rbnIpPoolThreshold addresses.

		Additionally, the action of sending the trap and/or log message
		is subject to the values of rbnIpPoolSendTrap and
		rbnIpPoolLogMessage.

		A value of zero means there is no threshold."
	::= { rbnIpPoolEntry 9 }

rbnIpPoolSendTrap OBJECT-TYPE
	SYNTAX       TruthValue
	MAX-ACCESS   read-only
	STATUS       current
	DESCRIPTION
		"If true, upon detection of reaching a per-pool threshold
		event, a trap will be sent.  See the definition of the
		rbnIpPoolThresholdMet for the information included in the
		trap.

		Note, both rbnIpPoolSendTrap and rbnIpPoolLogMessage are
		allowed to be TRUE at the same time."
	::= { rbnIpPoolEntry 10 }

rbnIpPoolLogMessage OBJECT-TYPE
	SYNTAX       TruthValue
	MAX-ACCESS   read-only
	STATUS       current
	DESCRIPTION
		"If true, upon detection of reaching a per-pool threshold
		event, a message will be logged.  The information contained
		in the message is the same as that included in the
		rbnIpPoolThresholdMet trap.

		Note, both rbnIpPoolSendTrap and rbnIpPoolLogMessage are
		allowed to be TRUE at the same time."
	::= { rbnIpPoolEntry 11 }


--
-- IP Pool per context objects
--

rbnIpPoolSummary          OBJECT IDENTIFIER ::= { rbnIpPoolMIBObjects 2 }

rbnIpPoolContextName OBJECT-TYPE
	SYNTAX       SnmpAdminString (SIZE (0..63))
	MAX-ACCESS   read-only
	STATUS       current
	DESCRIPTION
		"The name of the context containing the IP Pool."
	::= { rbnIpPoolSummary 1 }

rbnIpPoolContextAvailable OBJECT-TYPE
	SYNTAX       Unsigned32
	MAX-ACCESS   read-only
	STATUS       current
	DESCRIPTION
		"The total number of ip addresses available in all pools of
		 all interfaces in the context valid in the current view."
	::= { rbnIpPoolSummary 2 }

rbnIpPoolContextThreshold OBJECT-TYPE
	SYNTAX       Unsigned32
	MAX-ACCESS   read-only
	STATUS       current
	DESCRIPTION
		"The per-context threshold of an IP Pool is the value for
		currently available per-context addresses, as reported in
		rbnIpPoolContextAvailable, which causes a trap and/or
		log message to be generated when this value is reached.

		This is a falling threshold, so a trap and/or log message
		will only be sent on a transition of the value of available
		addresss from (rbnIpPoolContextThreshold+1) addresses to
		rbnIpPoolContextThreshold addresses.

		Additionally, the action of sending the trap and/or log message
		is subject to the values of rbnIpPoolContextSendTrap and
		rbnIpPoolContextLogMessage.

		A value of zero means there is no per-context threshold."
	::= { rbnIpPoolSummary 3 }

rbnIpPoolContextSendTrap OBJECT-TYPE
	SYNTAX       TruthValue
	MAX-ACCESS   read-only
	STATUS       current
	DESCRIPTION
		"If true, upon detection of a per-context threshold crossing
		event, a trap will be sent.  See the definition of the
		rbnIpPoolContextThresholdMet for the information included
		in the trap.

		Note, both rbnIpPoolContextSendTrap and
		rbnIpPoolContextLogMessage are allowed to be true at the
		same time."
	::= { rbnIpPoolSummary 4 }

rbnIpPoolContextLogMessage OBJECT-TYPE
	SYNTAX       TruthValue
	MAX-ACCESS   read-only
	STATUS       current
	DESCRIPTION
		"If true, upon detection of a per-context threshold crossing
		event, a message will be logged.  The information contained
		in the message logged is the same as that included in the
		rbnIpPoolContextThresholdMet trap.

		Note, both rbnIpPoolContextSendTrap and
		rbnIpPoolContextLogMessage are allowed to be true at the
		same time."
	::= { rbnIpPoolSummary 5 }


-- definition of IP Pool related notifications.

rbnIpPoolThresholdMet NOTIFICATION-TYPE
	OBJECTS {
		rbnIpPoolContextName,
		rbnIpPoolInterfaceName,
		rbnIpPoolMask,
		rbnIpPoolAvailable,
		rbnIpPoolThreshold }
	STATUS	current
	DESCRIPTION
		"A notification indicating that the per pool falling
		 threshold has been reached."
	::= { rbnIpPoolMIBNotifications 1 }

rbnIpPoolContextThresholdMet NOTIFICATION-TYPE
	OBJECTS {
	    rbnIpPoolContextName,
	    rbnIpPoolContextAvailable,
	    rbnIpPoolContextThreshold
	}
	STATUS	current
	DESCRIPTION
		"A notification indicating that the per context falling
		 threshold has been reached."
	::= { rbnIpPoolMIBNotifications 2 }

--
-- Compliance statements
--

rbnIpPoolCompliances OBJECT IDENTIFIER ::= { rbnIpPoolMIBConformance 1 }
rbnIpPoolGroups      OBJECT IDENTIFIER ::= { rbnIpPoolMIBConformance 2 }

rbnIpPoolGroup	OBJECT-GROUP
	OBJECTS {
		rbnIpPoolInterfaceName,
		rbnIpPoolMask,
		rbnIpPoolSize,
		rbnIpPoolAvailable,
		rbnIpPoolUnusable,
		rbnIpPoolInuse,
		rbnIpPoolThreshold,
		rbnIpPoolSendTrap,
		rbnIpPoolLogMessage,
		rbnIpPoolContextName,
		rbnIpPoolContextAvailable,
		rbnIpPoolContextThreshold,
		rbnIpPoolContextSendTrap,
		rbnIpPoolContextLogMessage
	}
	STATUS	current
	DESCRIPTION
		"The collection of objects providing interface IP Pool
                 information."
	::= { rbnIpPoolGroups 1}

rbnIpPoolNotifyGroup NOTIFICATION-GROUP
	NOTIFICATIONS {
		rbnIpPoolThresholdMet,
		rbnIpPoolContextThresholdMet
	}
	STATUS	current
	DESCRIPTION
        	"The collection of notifications related to IP Pools."
	::= { rbnIpPoolGroups 2}

rbnIpPoolCompliance MODULE-COMPLIANCE
	STATUS       current
	DESCRIPTION
		"The compliance statement for SNMP entities which implement
		 the Redback IP Pool MIB."
	MODULE      -- this module
	MANDATORY-GROUPS {
		rbnIpPoolGroup,
		rbnIpPoolNotifyGroup
	}
	::= { rbnIpPoolCompliances 1}

END
