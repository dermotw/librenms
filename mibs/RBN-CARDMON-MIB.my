-- *****************************************************************
-- RBN-CARDMON-MIB              Card Monitor MIB
--
-- Copyright (c) 2004 RedBack Networks, Inc.
-- All rights reserved.
-- 
-- *****************************************************************

RBN-CARDMON-MIB DEFINITIONS ::= BEGIN

IMPORTS
        MODULE-IDENTITY,
        OBJECT-TYPE,
        NOTIFICATION-TYPE,
        Unsigned32
                FROM SNMPv2-SMI
        MODULE-COMPLIANCE,
        OBJECT-GROUP,
        NOTIFICATION-GROUP
                FROM SNMPv2-CONF
        SnmpAdminString
                FROM SNMP-FRAMEWORK-MIB
        DateAndTime
                FROM SNMPv2-TC
        RbnSlot
                FROM RBN-TC
        RbnAlarmType,
        RbnAlarmProbableCause,
        RbnAlarmPerceivedSeverity,
        RbnAlarmId
                FROM RBN-ALARM-TC
        rbnMgmt
                FROM RBN-SMI;

rbnCardMonMIB MODULE-IDENTITY
        LAST-UPDATED    "200406290000Z" -- Jun 29, 2004
        ORGANIZATION    "RedBack Networks, Inc."
        CONTACT-INFO
                "       RedBack Networks, Inc.

                Postal: 300 Holger Way
                        San Jose, CA  95134
                        USA

                 Phone: +1 408 750 5000
                   Fax: +1 408 750 5599

                E-mail: mib-info@redback.com"
        DESCRIPTION
                "The MIB used to manage the Controller, I/O and
                System Card Monitor functionality on RedBack 
                Networks devices."
        REVISION        "200406290000Z" -- Jun 29, 2004
        DESCRIPTION
                "Initial version."
        ::= { rbnMgmt 31 }

rbnCardMonMIBNotifications OBJECT IDENTIFIER
        ::= { rbnCardMonMIB 0 }

rbnCardMonMIBObjects OBJECT IDENTIFIER
        ::= { rbnCardMonMIB 1 }

rbnCardMonMIBConformance OBJECT IDENTIFIER
        ::= { rbnCardMonMIB 2 }


-- Textual Conventions


-- MIB Objects

rbnCardAlarmActiveTable OBJECT-TYPE
        SYNTAX      SEQUENCE OF RbnCardAlarmActiveEntry
        MAX-ACCESS  not-accessible
        STATUS      current
        DESCRIPTION
                "This table contains the card alarms currently
                active on the system."
        ::= { rbnCardMonMIBObjects 1 }

rbnCardAlarmActiveEntry OBJECT-TYPE
        SYNTAX      RbnCardAlarmActiveEntry
        MAX-ACCESS  not-accessible
        STATUS      current
        DESCRIPTION
                "Entries appear in this table when alarms are
                raised. They are removed when the alarms are cleared."
        INDEX   { rbnCardAlarmSlot, rbnCardAlarmActiveIndex }
        ::= { rbnCardAlarmActiveTable 1 }

RbnCardAlarmActiveEntry ::= SEQUENCE {
        rbnCardAlarmSlot                RbnSlot,
        rbnCardAlarmActiveIndex         Unsigned32,
        rbnCardAlarmId                  RbnAlarmId,
        rbnCardAlarmType                RbnAlarmType,
        rbnCardAlarmDateAndTime         DateAndTime,
        rbnCardAlarmDescription         SnmpAdminString,
        rbnCardAlarmProbableCause       RbnAlarmProbableCause,
        rbnCardAlarmSeverity            RbnAlarmPerceivedSeverity
}

rbnCardAlarmSlot OBJECT-TYPE
        SYNTAX      RbnSlot
        MAX-ACCESS  not-accessible
        STATUS      current
        DESCRIPTION
                "The chassis slot number in which the card is present."
        ::= { rbnCardAlarmActiveEntry 1 }

rbnCardAlarmActiveIndex OBJECT-TYPE
        SYNTAX      Unsigned32 (1..4294967295)
        MAX-ACCESS  not-accessible
        STATUS      current
        DESCRIPTION
                "A monotonically increasing integer index. It wraps
                back to 1 after it reaches its maximum value."
        ::= { rbnCardAlarmActiveEntry 2 }

rbnCardAlarmId OBJECT-TYPE 
        SYNTAX      RbnAlarmId
        MAX-ACCESS  read-only
        STATUS      current
        DESCRIPTION
                "An identifier for the alarm."
        ::= { rbnCardAlarmActiveEntry 3 }

rbnCardAlarmType OBJECT-TYPE 
        SYNTAX      RbnAlarmType
        MAX-ACCESS  read-only
        STATUS      current
        DESCRIPTION
                "The type of the alarm."
        ::= { rbnCardAlarmActiveEntry 4 }

rbnCardAlarmDateAndTime OBJECT-TYPE 
        SYNTAX      DateAndTime
        MAX-ACCESS  read-only
        STATUS      current
        DESCRIPTION
                "The local date and time when the alarm was raised"
        ::= { rbnCardAlarmActiveEntry 5 }

rbnCardAlarmDescription OBJECT-TYPE 
        SYNTAX      SnmpAdminString (SIZE(0..64))
        MAX-ACCESS  read-only
        STATUS      current
        DESCRIPTION
                "A text string which conveys additional information
                about the alarm."
        ::= { rbnCardAlarmActiveEntry 6 }

rbnCardAlarmProbableCause OBJECT-TYPE 
        SYNTAX      RbnAlarmProbableCause
        MAX-ACCESS  read-only
        STATUS      current
        DESCRIPTION
                "The probable cause for this alarm."
        ::= { rbnCardAlarmActiveEntry 7 }

rbnCardAlarmSeverity OBJECT-TYPE 
        SYNTAX      RbnAlarmPerceivedSeverity
        MAX-ACCESS  read-only
        STATUS      current
        DESCRIPTION
                "The perceived severity of the alarm."
        ::= { rbnCardAlarmActiveEntry 8 }


-- Notifications

rbnCardAlarm NOTIFICATION-TYPE
        OBJECTS     {
                        rbnCardAlarmId,
                        rbnCardAlarmType,
                        rbnCardAlarmDateAndTime,
                        rbnCardAlarmDescription,
                        rbnCardAlarmProbableCause,
                        rbnCardAlarmSeverity
                    }
        STATUS      current
        DESCRIPTION
                "An rbnCardAlarm notification signifies that an
                alarm has been raised/cleared on a controller,
                system or i/o card."
        ::= { rbnCardMonMIBNotifications 1 }

-- Conformance Statements

rbnCardMonMIBGroups OBJECT IDENTIFIER
        ::= { rbnCardMonMIBConformance 1 }

rbnCardMonMIBCompliances OBJECT IDENTIFIER
        ::= { rbnCardMonMIBConformance 2 }

rbnCardMonMIBObjectGroup OBJECT-GROUP
      OBJECTS     {   rbnCardAlarmId, rbnCardAlarmType,
                      rbnCardAlarmDateAndTime, rbnCardAlarmDescription,
                      rbnCardAlarmProbableCause, rbnCardAlarmSeverity
                  }
      STATUS      current
      DESCRIPTION
              "A collection of objects providing card monitor
              information."
      ::= { rbnCardMonMIBGroups 1 }

rbnCardMonMIBNotificationGroup NOTIFICATION-GROUP
      NOTIFICATIONS   {   rbnCardAlarm
                      }
      STATUS      current
      DESCRIPTION
              "A collection of notifications providing card
              monitor information."
      ::= { rbnCardMonMIBGroups 2 }

rbnCardMonMIBCompliance MODULE-COMPLIANCE
      STATUS      current
      DESCRIPTION
              "The compliance statement for the Card Monitor MIB"
      MODULE      -- this module
      GROUP       rbnCardMonMIBObjectGroup
      DESCRIPTION
              "This group is mandatory for devices which contain
              Card Monitoring capabilities"
      GROUP       rbnCardMonMIBNotificationGroup
      DESCRIPTION
              "This group is mandatory for devices which contain
              Card Monitoring capabilities"
      ::= { rbnCardMonMIBCompliances 1 }

END
